;; HELLOWORLD - prints a greeting without changing the drawing.
;; No inputs. Returns nothing visible after the greeting.
(defun C:HELLOWORLD ()
  (alert (princ "\nHello, world! Loaded from GitHub with GitLISP."))
  (princ)
)

(princ)
